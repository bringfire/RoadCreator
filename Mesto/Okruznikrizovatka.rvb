Option Explicit
'Script written by <insert name>
'Script copyrighted by <insert company name>
'Script version 18. prosince 2015 18:29:38

Call Okruznikrizovatka()
Sub Okruznikrizovatka()
	Dim stred,vnejsiprumer,pocetramen
	
	
	Rhino.CurrentView "Shora"
	stred = Rhino.GetPoint("Vyber stred okruzni krizovatky")
	If IsNull(stred) Then
		Rhino.Print "Nevybral jste stred okruzni krizovatky"
		Exit Sub
	End If
	
	vnejsiprumer = Rhino.GetReal("Zadej vnejsi polomer", 25, 14, 50)
	If IsNull(vnejsiprumer) Then
		Rhino.Print "Nezadak jste vnejsi polomer"
		Exit Sub
	End If
	
	pocetramen = Rhino.GetReal("Zadej pocet ramen krizovatky", 4, 2, 6)
	If IsNull(pocetramen) Then
		Rhino.Print "Nezadak jste pocet ramen"
		Exit Sub
	End If
	If Rhino.IsLayer("Krizovatka") Then
		Rhino.CurrentLayer("Krizovatka")
	Else 
		Rhino.Print "New layer: " & Rhino.AddLayer("Krizovatka", RGB(0, 0, 0))
		Rhino.CurrentLayer("Krizovatka")
	End If
	'Dne normy
	Dim sirkapruhu,prstenec,vnejsiprumerkrivka,vnitrniprumerkrivka,prsteneckrivka
	
	If vnejsiprumer=>25 Then
		prstenec = 1
		If vnejsiprumer >= 28 Then 
			If vnejsiprumer >= 30 Then 
				If vnejsiprumer >= 32 Then 
					If vnejsiprumer >= 35 Then 
						If vnejsiprumer >= 40 Then 
							sirkapruhu = 4.5
						Else
							sirkapruhu = 5.0
						End If
					Else
						sirkapruhu = 5.25
					End If
				Else
					sirkapruhu = 5.5
				End If
			Else
				sirkapruhu = 6.0
			End If
		Else
			sirkapruhu = 6.5
		End If
	Else
		sirkapruhu = Rhino.GetReal("Zadej sirku pruhu", 5, 4, vnejsiprumer / 2)
		If IsNull(vnejsiprumer) Then
			Rhino.Print "Nazadal jste sirku pruhu"
			Exit Sub
		End If
		
	End If
	
	vnejsiprumerkrivka = Rhino.AddCircle(stred, vnejsiprumer / 2)
	vnitrniprumerkrivka = Rhino.AddCircle(stred, (vnejsiprumer / 2) - sirkapruhu)
	
	If vnejsiprumer >= 25 Then
		prsteneckrivka = Rhino.AddCircle(stred, (vnejsiprumer / 2) - sirkapruhu - prstenec)
	End If
	
	Dim rameno,osaramene,bodramene,p,bodyramene(1),prusecik,pomline
	ReDim rameno(pocetramen-1)
	ReDim osaramene(pocetramen-1)
	ReDim bodramene(pocetramen-1)
	ReDim prusecik(pocetramen-1)
	bodyramene(0) = stred
	p = 0
	Do While p < pocetramen
		rameno(p) = Rhino.GetPoint("Zadej smer " & CStr(p + 1) & ". ramene krizovatky(Postupuj proti smeru hodinovych rucicek", stred, (vnejsiprumer / 2) + 20)
		If IsNull(rameno(p)) Then
			Rhino.Print "Nezadal jste smer ramene"
			Exit Sub
		End If
		pomline = Rhino.AddLine(stred, rameno(p))
		prusecik(p) = Rhino.CurveCurveIntersection(pomline, vnejsiprumerkrivka)
		bodyramene(0) = prusecik(p)(0, 1)
		bodyramene(1) = rameno(p)
		Rhino.DeleteObject(pomline)
		osaramene(p) = Rhino.Addcurve(bodyramene)
		bodramene(p) = Rhino.AddPoint(rameno(p))
		Rhino.AddText "" & CStr(p + 1) & "", rameno(p), 3
		p = p + 1
		
	Loop
	Rhino.EnableRedraw vbFalse
	'Tvorba hran a zaobleni hran
	
	Dim HranaL(),HranaP(),SirkaL(),SirkaP(),souradnice,Hranakrizovatky(),polomer(),profil(),Startbod,Endbod
	ReDim HranaL(pocetramen-1)
	ReDim HranaP(pocetramen-1)
	ReDim SirkaL(pocetramen-1)
	ReDim SirkaP(pocetramen-1)
	ReDim Hranakrizovatky(2*pocetramen-1)
	ReDim polomer(2*pocetramen-1)
	ReDim profil(pocetramen-1)
	ReDim Startbod(pocetramen-1)
	ReDim Endbod(pocetramen-1)
	p = 0
	Do While p < pocetramen
		SirkaP(p) = Rhino.GetReal("Zadej sirku vjezdu ramene cislo" & CStr(p + 1) & ".", 3)
		polomer(2 * p) = Rhino.GetReal("Zadej polomer vjezdu " & CStr(p + 1) & ". rameneme", 8, 6, 17)
		Rhino.RotateObject bodramene(p), stred, +50
		souradnice = Rhino.PointCoordinates(bodramene(p))
		HranaP(p) = Rhino.Offsetcurve(osaramene(p), souradnice, SirkaP(p))
		Hranakrizovatky(2 * p) = Rhino.FilletCurves(HranaP(p)(0), Rhino.CurveMidPoint(HranaP(p)(0)), vnejsiprumerkrivka, souradnice, polomer(2 * p), True)
		Rhino.RotateObject bodramene(p), stred, -50
		Startbod(p) = Rhino.CurveEndPoint(HranaP(p)(0))
		If IsArray(Hranakrizovatky) Then
			Call Rhino.DeleteObject(HranaP(p)(0))
		End If
		
		SirkaL(p) = Rhino.GetReal("Zadej sirku vyjezdu ramene cislo" & CStr(p + 1) & ".", 3)
		polomer((2 * p) + 1) = Rhino.GetReal("Zadej polomer vyjezdu " & CStr(p + 1) & ". rameneme", 12, 12)
		Rhino.RotateObject bodramene(p), stred, -50
		souradnice = Rhino.PointCoordinates(bodramene(p))
		HranaL(p) = Rhino.Offsetcurve(osaramene(p), souradnice, SirkaL(p))
		Hranakrizovatky((2 * p) + 1) = Rhino.FilletCurves(HranaL(p)(0), Rhino.CurveMidPoint(HranaL(p)(0)), vnejsiprumerkrivka, souradnice, polomer((2 * p) + 1), True)
		Rhino.RotateObject bodramene(p), stred, +50
		Endbod(p) = Rhino.CurveEndPoint(HranaL(p)(0))
		If IsArray(Hranakrizovatky) Then
			Call Rhino.DeleteObject(HranaL(p)(0))
		End If
		
		Rhino.MoveObject osaramene(p), Rhino.CurveStartPoint(osaramene(p)), Rhino.PointCoordinates(bodramene(p))		
		Rhino.ScaleObject osaramene(p), Rhino.CurveStartPoint(osaramene(p)), Array(0.5, 0.5, 0.5)
		profil(p) = Rhino.AddLine(Startbod(p), Endbod(p))
		p = p + 1
	Loop
	
	'Tvorba ploch
	Dim Oblouk(),Plochakrivkyramene(3),pomplocha
	ReDim Oblouk(pocetramen-1)
	p = 0
	Do While p < pocetramen
		Startbod = Rhino.CurveEndPoint(Hranakrizovatky(2 * p)(0))
		Endbod = Rhino.CurveEndPoint(Hranakrizovatky((2 * p) + 1)(0))
		Oblouk(p) = Rhino.AddArc3Pt(Startbod, Endbod, prusecik(p)(0, 1))
		Plochakrivkyramene(0) = profil(p)
		Plochakrivkyramene(1) = oblouk(p)
		Plochakrivkyramene(2) = Hranakrizovatky(2 * p)(0)
		Plochakrivkyramene(3) = Hranakrizovatky((2 * p) + 1)(0)
		Rhino.AddPlanarSrf(Plochakrivkyramene)
		p = p + 1
	Loop
	
	ReDim Plochakrivkyramena(1)
	Plochakrivkyramene(0) = vnejsiprumerkrivka
	Plochakrivkyramene(1) = vnitrniprumerkrivka
	Rhino.AddPlanarSrf(Plochakrivkyramene)
	
	If vnejsiprumer >= 25 Then
		Plochakrivkyramene(0) = vnitrniprumerkrivka
		Plochakrivkyramene(1) = prsteneckrivka
		Rhino.AddPlanarSrf(Plochakrivkyramene)
		pomplocha = Rhino.AddPlanarSrf(prsteneckrivka)
		Rhino.MoveObject pomplocha(0), Array(0, 0, 0), Array(0, 0, 0.75)
		Rhino.ExtrudeCurveStraight prsteneckrivka, Array(0, 0, 0), Array(0, 0, 0.75)
		
	Else
		Rhino.AddPlanarSrf(vnitrniprumerkrivka)
	End If
	
	If Rhino.IsLayer("Default") Then
		Rhino.CurrentLayer("Default")
	Else 
		Rhino.Print "New layer: " & Rhino.AddLayer("Default", RGB(0, 0, 0))
		Rhino.CurrentLayer("Default")
	End If
	Rhino.EnableRedraw vbTrue
End Sub
