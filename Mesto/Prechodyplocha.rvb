Option Explicit
'Script written by <insert name>
'Script copyrighted by <insert company name>
'Script version 8. ledna 2016 10:28:08

Call Prechodyplocha()
Sub Prechodyplocha()
	Dim plochasilnice,startpoint,endpoint,sirka,angle,prechod
	
	plochasilnice = Rhino.GetObject("Vyber silnici na kterou chces umistit prechod", 24)
	If IsNull(plochasilnice) Then
		Rhino.Print "Nyvybral si silnici"
		Exit Sub
	End If
	
	startpoint = Rhino.Getpoint("Vyber zacatek prechodu")
	If IsNull(startpoint) Then
		Rhino.Print "Nyvybral si zacatek prechodu"
		Exit Sub
	End If
	
	endpoint = Rhino.Getpoint("Vyber konec prechodu", startpoint)
	If IsNull(endpoint) Then
		Rhino.Print "Nyvybral si konec prechodu"
		Exit Sub
	End If
	
	sirka = Rhino.GetReal("Urci sirku prechodu", 4)
	If IsNull(sirka) Then
		Rhino.Print "Nezadal si sirku prechodu"
		Exit Sub
	End If
	If Rhino.IsLayer("Prechod") Then
		Rhino.CurrentLayer("Prechod")
	Else 
		Rhino.Print "New layer: " & Rhino.AddLayer("Prechod", RGB(0, 0, 0))
		Rhino.CurrentLayer("Prechod")
	End If
	
	Rhino.EnableRedraw vbFalse

	prechod = Rhino.AddPlaneSurface(Rhino.WorldXYPlane, sirka, Rhino.Distance(startpoint, endpoint) * 2)
	Rhino.MoveObject prechod, Array(0, 0, 0), Array(-sirka / 2, 0, 0)
	angle = Rhino.Angle(startpoint, endpoint)
	Rhino.MoveObject prechod, Array(0, +Rhino.Distance(startpoint, endpoint) / 2, 0), startpoint 
	
	Rhino.Rotateobject prechod, startpoint, (angle(0) + 270)
	Rhino.SplitBrep plochasilnice, prechod, True
	Rhino.DeleteObject prechod
	
	If Rhino.IsLayer("Default") Then
		Rhino.CurrentLayer("Default")
	Else 
		Rhino.Print "New layer: " & Rhino.AddLayer("Default", RGB(0, 0, 0))
		Rhino.CurrentLayer("Default")
	End If
	Rhino.EnableRedraw vbTrue
	
	
End Sub
