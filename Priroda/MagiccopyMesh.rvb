Option Explicit
'Script written by <Adam Orlicky>
'Script copyrighted by <insert company name>
'Script version 28. dubna 2015 10:34:35
Call MagiccopyMesh()

Function Joinmore(objects)
	Dim pieces,pomoc
	Rhino.EnableRedraw vbFalse
	If (Ubound(Objects)) = 0Then
		pomoc = Rhino.CopyObject(objects(0), Array(0, 0, 0), Array(0, 0, 0))
		joinmore = pomoc
	Else
		For Each pieces In objects
			Call Rhino.Command("_SelID " & pieces & "_Enter", 0)
		Next
		Call Rhino.Command("_Join", 0)
		pomoc = Rhino.LastCreatedObjects
		joinmore = pomoc(0)
	End If
	Rhino.UnselectAllObjects
	Rhino.EnableRedraw vbTrue
End Function


Sub MagiccopyMesh()	
	'Ziskani objektu od uzivatele pro kopirovani
	Dim Objekt,pieces,Base,Scale,teren,terenpomoc
	teren = Rhino.GetObjects("Vyber teren", 32)
	If IsNull(teren) Then
		Rhino.Print "Nevybral jste teren"
		Exit Sub
	End If
	
	If (Ubound(Teren)) > 0Then
		For Each pieces In Teren
			rhino.CopyObject pieces, Array(0, 0, 0), Array(0, 0, 0)
		Next
		
	End If
	If Rhino.IsLayer("Stromy databaze") Then
		Rhino.LayerLocked "Stromy databaze", False
		Rhino.LayerVisible "Stromy databaze", True
		Rhino.Print" Byla zpristupnena databaze stromu a keru"
	End If
	
	Objekt = Rhino.Getobjects("Vyber objekt pro kopirovani")
	If IsNull(Objekt) Then
		Rhino.Print "Nevybral jste objekt pro kopirovani"
		If Rhino.IsLayer("Stromy databaze") Then
			Rhino.LayerLocked "Stromy databaze", True
			Rhino.LayerVisible "Stromy databaze", False
		End If
		Exit Sub
	End If
	Base = Rhino.GetPoint("Vyber pocatek kopirovani")
	If IsNull(Base) Then
		Rhino.Print "Nevybral jste pocatek"
		If Rhino.IsLayer("Stromy databaze") Then
			Rhino.LayerLocked "Stromy databaze", True
			Rhino.LayerVisible "Stromy databaze", False
		End If
		Exit Sub
	End If
	Scale = Rhino.GetReal("Zadej rozsah zmeny meřítka v %")
	If IsNull(Scale) Then
		Rhino.Print "Nezadal jste rozsah meritka"
		If Rhino.IsLayer("Stromy databaze") Then
			Rhino.LayerLocked "Stromy databaze", True
			Rhino.LayerVisible "Stromy databaze", False
		End If
		Exit Sub
	End If
	'Pomocny teren
	terenpomoc = joinmore(Teren)
	'Kopirovani objektu s natocenim'
	Dim Point, i, copy, rand, randscale
	i = 0
	
	If Rhino.IsLayer("Stromy") Then
		Rhino.CurrentLayer("Stromy")
	Else 
		Rhino.Print "New layer: " & Rhino.AddLayer("Stromy", RGB(0, 190, 0))
		Rhino.CurrentLayer("Stromy")
	End If
	Do While i = 0
		Point = Rhino.GetPointOnMesh(Terenpomoc, "Vyber místo pro zkopírování")
		
		If IsNull(Point) Then
			Rhino.DeleteObject Terenpomoc
			If Rhino.IsLayer("Default") Then
				Rhino.CurrentLayer("Default")
			Else 
				Rhino.Print "New layer: " & Rhino.AddLayer("Default", RGB(0, 0, 0))
				Rhino.CurrentLayer("Default")
			End If
			If Rhino.IsLayer("Stromy databaze") Then
				Rhino.LayerLocked "Stromy databaze", True
				Rhino.LayerVisible "Stromy databaze", False
			End If
			Exit Sub
		End If
		
		copy = Rhino.CopyObjects(Objekt, Base, Point)
		'Nahodne cislo pro pootoceni objektu'
		Randomize
		Rhino.ObjectLayer copy, "Stromy"
		rand = ((360) * Rnd)
		Rhino.RotateObjects copy, Point, rand
		'Nahodne cislo pro pootoceni objektu'
		randscale = (((Scale) * Rnd + 1) - (Scale / 2)) / 100 + 1
		Rhino.ScaleObjects copy, Point, array(randscale, randscale, randscale)
	Loop
	
End Sub
