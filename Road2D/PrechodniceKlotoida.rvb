Option Explicit
'Script written by <insert name>
'Script copyrighted by <insert company name>
'Script version 18. února 2015 11:56:38

Function cosin(x)
	Dim prepo,A,B,disprepona,disproti
	A = Array(0, 0, 0)
	B = Array(1, 0, 0)
	prepo = Rhino.AddLine(A, B)
	Rhino.RotateObject prepo, A, x
	B = Rhino.CurveEndPoint(prepo)
	disproti = Rhino.Angle(A, B)
	Rhino.DeleteObject(prepo)
	cosin = disproti(2)
	
End Function

Function sinus(x)
	Dim prepo,A,B,disprepona,disproti
	A = Array(0, 0, 0)
	B = Array(1, 0, 0)
	prepo = Rhino.AddLine(A, B)
	Rhino.RotateObject prepo, A, x
	B = Rhino.CurveEndPoint(prepo)
	disproti = Rhino.Angle(A, B)
	Rhino.DeleteObject(prepo)
	sinus = disproti(3)
	
End Function

Function Split(brep, cutter)
	
	Dim saved, cmd
	split = Null
	saved = Rhino.SelectedObjects
	Rhino.UnSelectAllObjects
	Rhino.SelectObject brep
	cmd = "_Split _SelID " & cutter & " _Enter"
	Rhino.Command cmd, 0
	split = Rhino.LastCreatedObjects
	Rhino.UnSelectAllObjects
	If IsArray(saved) Then Rhino.SelectObjects(saved)
End Function

Sub PrechodniceKlotoida()
	If Rhino.IsLayer("Vrstevnice") Then
		Rhino.LayerLocked "Vrstevnice", True
	End If
	If Rhino.IsLayer("Hlavni vrstevnice") Then
		Rhino.LayerLocked "Hlavni vrstevnice", True
	End If
	If Rhino.IsLayer("TEREN") Then
		Rhino.LayerLocked "TEREN", True
	End If
	
	'Ziskavani parametru od uzivatele'
	Rhino.CurrentView "Shora"
	Dim L,R,tec1,tec2,vrch,vrchol
	tec1 = Rhino.GetObject("Vyber první část tečnového polygonu", 4)
	If IsNull(tec1) Then
		Rhino.Print "Nevybral jste první část tečnového polygonu"
		Exit Sub
	End If
	tec2 = Rhino.GetObject("Vyber druhou část tečnového polygonu", 4)
	If IsNull(tec2) Then
		Rhino.Print "Nevybral jste druhou část tečnového polygonu"
		Exit Sub
	End If
	L = Rhino.GetReal("Zadej delku prechodnice klotoidy:", 60, 5, 500)	
	If IsNull(L) Then
		Rhino.Print "Nezadal jste delku prechodnice"
		Exit Sub
	End If
	R = Rhino.GetReal("Zadejte polomer navazujícího kružnicového oblouku R:", 200, 5, 2000)	
	If IsNull(R) Then
		Rhino.Print "Nezadal polomer navazujícího kružnicového oblouku R"
		Exit Sub
	End If
	If R > 800 Then
		Rhino.Print"Pokud platí, že R>= 0.375 * Vn(s)* Vn(s) a zaroven R>=800 m NEMUSI se vkladat prechodnice"
	End If
	
	Rhino.EnableRedraw vbFalse
	vrch = Rhino.CurveCurveIntersection(tec1, tec2)
	If IsNull(vrch) Then
		Rhino.Print "Nejedná se o tečny s prusečíkem"
		Rhino.EnableRedraw vbTrue
		Exit Sub
	End If
	vrchol = vrch(0, 1)
	
	'Pomocne parametry'
	Dim X,Y,i,delkaseg,arrpoint(25),prech,A,pocatek
	pocatek = Array(0, 0, 0)
	delkaseg = L / 25
	A = L * R
	i = 0
	
	'Cyklus pro vykreslení bodů'
	Do While i <= 25
		If i = 0 Then
			X = 0
			Y = 0
		Else 
			l = delkaseg * i
			r = A / l
			X = l - ((l ^ 3) / (40 * (r ^ 2))) + ((l ^ 5) / (3456 * (r ^ 4)))
			Y = ((l ^ 2) / (6 * (r ^ 1))) - ((l ^ 4) / (336 * (r ^ 3))) + ((l ^ 6) / (42240 * (r ^ 5)))
			'Rhino.Print " " & CStr(X) & " ; " & CStr(Y) 
		End If
		arrpoint(i) = Array(X, Y, 0)
		i = i + 1
	Loop
	
	prech = Rhino.AddInterpCurve(arrpoint)
	'Ziskani uhlu'
	Dim kruz, pru1,pru2,alfa,tecline1(1),tecline2(1),beta,alfa1
	kruz = Rhino.AddCircle(vrchol, 1)
	pru1 = Rhino.CurveCurveIntersection(tec1, kruz)
	'Rhino.AddPoint pru1(0, 1)
	pru2 = Rhino.CurveCurveIntersection(tec2, kruz)
	'Rhino.AddPoint pru2(0, 1)
	Rhino.DeleteObject(kruz)
	tecline1(0) = pru1(0, 1)
	tecline1(1) = vrchol
	tecline2(0) = pru2(0, 1)
	tecline2(1) = vrchol
	alfa1 = Rhino.Angle2(tecline1, tecline2)
	alfa = 180 - alfa1(0)
	beta = Rhino.Angle(pru1(0, 1), vrchol)
	'Rhino.Print "alfa: " & CStr(alfa)
	'Rhino.Print "beta: " & CStr(beta(0))
	
	'Velka tecna'
	Dim Xs,m,tec,veltec
	Xs = L / 2 - ((L ^ 3) / (240 * (R ^ 2)))
	m = ((L ^ 2) / (24 * R)) - ((L ^ 4) / (2688 * (R ^ 3)))
	tec = (R + m) * ( sinus(alfa / 2) / Cosin(alfa / 2))
	Rhino.Print "m: " & CStr(m)
	Rhino.Print "Xs: " & CStr(tec)
	veltec = tec + Xs
	Rhino.Print "Velka tecna je : " & CStr(veltec)
	
	'Zacatek prechodnice a natoceni umisteni
	kruz = Rhino.AddCircle(vrchol, veltec)
	pru1 = Rhino.CurveCurveIntersection(tec1, kruz)
	If IsNull(pru1) Then
		Rhino.Print "První tečna je příliš krátká a zadaný oblouk se nevejde "
		Rhino.DeleteObject(kruz)
		Rhino.DeleteObject prech
		Rhino.EnableRedraw vbTrue
		Exit Sub
	End If
	pru2 = Rhino.CurveCurveIntersection(tec2, kruz)
	If IsNull(pru2) Then
		Rhino.Print "Druhá tečna je příliš krátká a zadaný oblouk se nevejde "
		Rhino.DeleteObject(kruz)
		Rhino.DeleteObject prech
		Rhino.EnableRedraw vbTrue
		Exit Sub
	End If
	Rhino.DeleteObject(kruz)
	'Rhino.AddPoint pru1(0, 1)
	
	'vytvoreni druhe prech
	Dim pomline(1),midpoint,pomcurve
	pomline(0) = pru1(0, 1)
	pomline(1) = pru2(0, 1)
	pomcurve = Rhino.AddCurve(pomline)
	midpoint = Rhino.CurveMidPoint(pomcurve)
	Rhino.DeleteObject(pomcurve)
	
	'Pravotociví/Levotociví
	Dim PomPoint,Kolmiceline(1),Kolmice,smerline(1)
	PomPoint = Array(0, -10, 0)
	Kolmiceline(0) = pocatek
	Kolmiceline(1) = PomPoint
	Kolmice = Rhino.AddCurve(Kolmiceline)
	Rhino.MoveObject Kolmice, pocatek, vrchol
	Rhino.RotateObject Kolmice, vrchol, beta(0)
	PomPoint = Rhino.CurveEndPoint(Kolmice)
	'Rhino.AddPoint(PomPoint)
	Kolmiceline(0) = vrchol
	Kolmiceline(1) = PomPoint
	smerline(0) = vrchol
	smerline(1) = midpoint
	'Rhino.AddLine smerline(0), smerline(1)
	alfa = Rhino.Angle2(smerline, Kolmiceline)
	Rhino.DeleteObject(Kolmice)
	'Rhino.Print "uhle kolmice a smer: " & CStr(alfa(1))
	
	'Transformace prechodnice
	Pompoint = Array(10, 0, 0)
	If alfa(1) > 270 Then
		prech = Rhino.MirrorObject(prech, pocatek, PomPoint, False)
	End If
	Rhino.MoveObject prech, pocatek, pru1(0, 1)
	Rhino.RotateObject prech, pru1(0, 1), beta(0)
	Dim prech2
	prech2 = Rhino.MirrorObject(prech, vrchol, midpoint, True)


	'OBLOUK
	Dim kon1,kon2,pomkruz1,pomkruz2,pomkruz,pru3,pru4,midpointprech
	kon1 = Rhino.CurveEndPoint(prech)
	kon2 = Rhino.CurveEndPoint(prech2)
	
	pomline(0) = kon1
	pomline(1) = kon2
	pomcurve = Rhino.AddCurve(pomline)
	midpointprech = Rhino.CurveMidPoint(pomcurve)
	Rhino.DeleteObject(pomcurve)
	

	'Rhino.AddPoint(kon1)
	'Rhino.AddPoint(kon2)
	pomkruz1 = Rhino.AddCircle(kon1, R)
	pomkruz2 = Rhino.AddCircle(kon2, R)
	pru1 = Rhino.CurveCurveIntersection(pomkruz1, pomkruz2)
	pomline(0) = vrchol
	pomline(1) = midpointprech
	pomcurve = Rhino.AddCurve(pomline)
	
	'pruseciky pomocnych kruznic
	i = 0
	Do While i <= 1
		'Rhino.AddPoint pru1(i, 1)
		Dim Oblouk
		pomkruz = Rhino.AddCircle(pru1(i, 1), R)
		If i = 0 Then
			pru4 = Rhino.CurveCurveIntersection(Pomkruz, pomcurve)
			If Not IsNull(pru4) Then
				Oblouk = Rhino.AddArc3Pt(kon1, kon2, pru4(0, 1))
			End If
			
		Else
			pru3 = Rhino.CurveCurveIntersection(Pomkruz, pomcurve)
			If Not IsNull(pru3) Then
				Oblouk = Rhino.AddArc3Pt(kon1, kon2, pru3(0, 1))
			End If
		End If
		Rhino.DeleteObject(pomkruz)
		i = i + 1
	Loop
	Rhino.ObjectName prech, "Prechodnice"
	Rhino.ObjectName prech2, "Prechodnice"
	Rhino.ObjectName Oblouk, "Oblouk"
	Rhino.AddCircle rhino.CurveStartPoint(prech), 2
	Rhino.AddCircle rhino.CurveStartPoint(prech2), 2
	Rhino.AddCircle rhino.CurveStartPoint(oblouk), 2
	Rhino.AddCircle rhino.CurveEndPoint(oblouk), 2
	Rhino.DeleteObject pomcurve
	Rhino.DeleteObject pomkruz1
	Rhino.DeleteObject pomkruz2
	Dim rozdel(1),join
	rozdel(0) = split(tec1, prech)
	Rhino.DeleteObject rozdel(0)(1)
	rozdel(1) = split(tec2, prech2)
	Rhino.DeleteObject rozdel(1)(1)
	join = Rhino.JoinCurves(Array(oblouk, prech, prech2, rozdel(0)(0), rozdel(1)(0), rozdel(0)(2), rozdel(1)(2)), True)
	Rhino.ObjectName join, "Krivkaspojena"
	Rhino.EnableRedraw vbTrue
	Rhino.Print "Byl vytvoren oblouk se symetrickou prechodnici tvaru klotoidy o poloměru: " & CStr(R)

End Sub
